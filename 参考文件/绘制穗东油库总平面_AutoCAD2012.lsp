(vl-load-com)

(defun phl:p3 (x y) (vlax-3d-point (list x y 0.0)))

(defun phl:layer (name color lw / lays lay)
  (setq lays (vla-get-Layers *phl-doc*))
  (if (tblsearch "LAYER" name)
    (setq lay (vla-Item lays name))
    (setq lay (vla-Add lays name)))
  (vla-put-Color lay color)
  (if lw (vla-put-Lineweight lay lw))
  lay)

(defun phl:arr (vals / sa)
  (setq sa (vlax-make-safearray vlax-vbDouble (cons 0 (1- (length vals)))))
  (vlax-safearray-fill sa vals)
  sa)

(defun phl:pline (pts lay closed / vals obj)
  (setq vals '())
  (foreach p pts (setq vals (append vals (list (car p) (cadr p)))))
  (setq obj (vla-AddLightWeightPolyline *phl-ms* (phl:arr vals)))
  (vla-put-Layer obj lay)
  (if closed (vla-put-Closed obj :vlax-true))
  obj)

(defun phl:rect (x1 y1 x2 y2 lay)
  (phl:pline (list (list x1 y1) (list x2 y1) (list x2 y2) (list x1 y2)) lay T))

(defun phl:line (x1 y1 x2 y2 lay / obj)
  (setq obj (vla-AddLine *phl-ms* (phl:p3 x1 y1) (phl:p3 x2 y2)))
  (vla-put-Layer obj lay)
  obj)

(defun phl:circle (x y r lay / obj)
  (setq obj (vla-AddCircle *phl-ms* (phl:p3 x y) r))
  (vla-put-Layer obj lay)
  obj)

(defun phl:mtext (x y w h txt lay attach / obj)
  (setq obj (vla-AddMText *phl-ms* (phl:p3 x y) w txt))
  (vla-put-Layer obj lay)
  (vla-put-StyleName obj "CN")
  ;; AutoCAD 2012 IAcadMText uses the writable Height property.
  (vla-put-Height obj h)
  (vla-put-AttachmentPoint obj attach)
  (vla-put-InsertionPoint obj (phl:p3 x y))
  obj)

(defun phl:label (x y w h txt)
  (phl:mtext x y w h txt "TEXT" 5))

(defun phl:tank (x y tag product roof / c)
  (phl:circle x y 15.0 "TANK")
  (phl:circle x y 12.5 "TANK-THIN")
  (phl:line (- x 10.5) y (+ x 10.5) y "TANK-THIN")
  (phl:line x (- y 10.5) x (+ y 10.5) "TANK-THIN")
  (phl:label x (+ y 2.7) 24.0 1.8 tag)
  (phl:label x y 24.0 1.3 (strcat product "  10000m3"))
  (phl:label x (- y 2.7) 24.0 1.2 roof))

(defun phl:building (x1 y1 x2 y2 label / cx cy)
  (phl:rect x1 y1 x2 y2 "BUILDING")
  (setq cx (/ (+ x1 x2) 2.0) cy (/ (+ y1 y2) 2.0))
  (phl:label cx cy (- x2 x1 1.0) 1.6 label))

(defun phl:dim (x1 y1 x2 y2 tx ty txt / obj)
  (setq obj (vla-AddDimAligned *phl-ms* (phl:p3 x1 y1) (phl:p3 x2 y2) (phl:p3 tx ty)))
  (vla-put-Layer obj "DIM")
  (if txt (vla-put-TextOverride obj txt))
  obj)

(defun phl:arrow (x1 y1 x2 y2 lay / ang a1 a2)
  (phl:line x1 y1 x2 y2 lay)
  (setq ang (angle (list x1 y1) (list x2 y2)))
  (setq a1 (+ ang 2.65) a2 (- ang 2.65))
  (phl:line x2 y2 (+ x2 (* 4.0 (cos a1))) (+ y2 (* 4.0 (sin a1))) lay)
  (phl:line x2 y2 (+ x2 (* 4.0 (cos a2))) (+ y2 (* 4.0 (sin a2))) lay))

(defun phl:setup-style (/ styles st)
  (setq styles (vla-get-TextStyles *phl-doc*))
  (if (tblsearch "STYLE" "CN")
    (setq st (vla-Item styles "CN"))
    (setq st (vla-Add styles "CN")))
  (vla-put-FontFile st "C:\\Windows\\Fonts\\simfang.ttf")
  (vla-put-Width st 1.0)
  (vla-put-ActiveTextStyle *phl-doc* st))

(defun c:PHLZONING (/ acad savepath)
  (vl-load-com)
  (setq acad (vlax-get-acad-object)
        *phl-doc* (vla-get-ActiveDocument acad)
        *phl-ms* (vla-get-ModelSpace *phl-doc*))
  (vla-StartUndoMark *phl-doc*)
  (setvar "CMDECHO" 0)
  (setvar "OSMODE" 0)
  (setvar "INSUNITS" 6)
  (setvar "LUNITS" 2)
  (setvar "LUPREC" 2)
  (setvar "MEASUREMENT" 1)
  (setvar "DIMTXT" 1.8)
  (setvar "DIMASZ" 1.5)
  (setvar "DIMSCALE" 1.0)

  (phl:layer "WALL" 7 50)
  (phl:layer "PARTITION" 7 25)
  (phl:layer "ROAD" 8 35)
  (phl:layer "DIKE" 1 35)
  (phl:layer "ISODIKE" 1 25)
  (phl:layer "TANK" 7 35)
  (phl:layer "TANK-THIN" 8 18)
  (phl:layer "BUILDING" 7 25)
  (phl:layer "PIPE-IN" 30 35)
  (phl:layer "PIPE-OUT" 200 35)
  (phl:layer "FIRE-WATER" 5 30)
  (phl:layer "DRAIN" 4 25)
  (phl:layer "TEXT" 7 18)
  (phl:layer "DIM" 7 18)
  (phl:layer "GRID" 9 9)
  (phl:setup-style)

  ;; A. site boundary, coordinate grid and functional zoning (metres)
  (phl:rect 0.0 0.0 420.0 300.0 "WALL")
  (foreach xx '(50 100 150 200 250 300 350 400) (phl:line xx 0.0 xx 300.0 "GRID"))
  (foreach yy '(50 100 150 200 250) (phl:line 0.0 yy 420.0 yy "GRID"))
  (phl:line 0.0 155.0 420.0 155.0 "PARTITION")
  (phl:line 0.0 95.0 420.0 95.0 "PARTITION")
  (phl:line 230.0 0.0 230.0 95.0 "PARTITION")
  (phl:mtext 8.0 293.0 70.0 3.0 "I  储油区（库区深处）" "TEXT" 1)
  (phl:mtext 8.0 150.0 70.0 3.0 "II  辅助生产区" "TEXT" 1)
  (phl:mtext 8.0 90.0 85.0 3.0 "III  公路装卸发油区" "TEXT" 1)
  (phl:mtext 238.0 90.0 75.0 3.0 "IV  行政管理区" "TEXT" 1)

  ;; B. storage ring fire road, two tank groups and pump shelters
  (phl:rect 18.0 164.0 402.0 286.0 "ROAD")
  (phl:rect 24.0 170.0 396.0 280.0 "ROAD")
  (phl:label 210.0 282.5 180.0 1.8 "环形消防车道：总宽不小于6m，路面不小于4m，R不小于12m，净空不小于5m")
  (phl:line 0.0 225.0 18.0 225.0 "ROAD")
  (phl:line 402.0 225.0 420.0 225.0 "ROAD")
  (phl:mtext 5.0 226.5 28.0 1.5 "储罐区出入口1" "TEXT" 1)
  (phl:mtext 390.0 226.5 28.0 1.5 "储罐区出入口2" "TEXT" 1)

  (phl:rect 44.0 183.0 218.0 268.0 "DIKE")
  (phl:line 46.0 222.0 216.0 222.0 "ISODIKE")
  (phl:label 131.0 265.0 90.0 1.8 "汽油罐组防火堤（甲B类）")
  (phl:label 131.0 220.0 80.0 1.4 "组内隔堤（92号/95号分隔）")
  (phl:tank 72.0 245.0 "T-101" "92号汽油" "内浮顶")
  (phl:tank 114.0 245.0 "T-102" "92号汽油" "内浮顶")
  (phl:tank 156.0 245.0 "T-103" "92号汽油" "内浮顶")
  (phl:tank 93.0 201.0 "T-201" "95号汽油" "内浮顶")
  (phl:tank 135.0 201.0 "T-202" "95号汽油" "内浮顶")
  (phl:dim 87.0 274.0 99.0 274.0 93.0 276.5 "12m=0.4D")

  (phl:rect 253.0 191.0 392.0 252.0 "DIKE")
  (phl:label 322.5 249.0 90.0 1.8 "0号柴油罐组防火堤（丙A类）")
  (phl:tank 280.0 221.0 "T-301" "0号柴油" "固定顶")
  (phl:tank 322.0 221.0 "T-302" "0号柴油" "固定顶")
  (phl:tank 364.0 221.0 "T-303" "0号柴油" "固定顶")
  (phl:dim 295.0 258.0 307.0 258.0 301.0 260.5 "12m=0.4D")

  (phl:building 223.0 238.0 245.0 263.0 "汽油罐前泵棚/阀组")
  (phl:building 223.0 193.0 245.0 218.0 "柴油罐前泵棚/阀组")
  (phl:label 234.0 188.0 28.0 1.4 "均在防火堤外")
  (phl:line 46.0 186.0 212.0 186.0 "DRAIN")
  (phl:arrow 212.0 186.0 216.0 190.0 "DRAIN")
  (phl:line 255.0 194.0 386.0 194.0 "DRAIN")
  (phl:arrow 386.0 194.0 390.0 198.0 "DRAIN")
  (phl:label 150.0 180.0 130.0 1.3 "罐区排水沟及受控排水口；防火堤有效容积另行核算")

  ;; C. auxiliary production area
  (phl:building 18.0 110.0 70.0 140.0 "消防水池\P容积待消防计算")
  (phl:building 75.0 110.0 105.0 140.0 "消防泵房")
  (phl:building 110.0 110.0 136.0 140.0 "泡沫站\P泡沫液罐")
  (phl:building 143.0 110.0 174.0 140.0 "变配电间\P（非爆炸区）")
  (phl:building 181.0 110.0 207.0 140.0 "化验室")
  (phl:building 214.0 110.0 240.0 140.0 "机修间")
  (phl:building 247.0 110.0 277.0 140.0 "备品仓库")
  (phl:building 284.0 110.0 320.0 140.0 "油气回收装置\P非焚烧式")
  (phl:building 327.0 110.0 377.0 140.0 "含油污水/事故应急池\P低点布置，容积待核算")
  (phl:rect 12.0 99.0 402.0 105.0 "ROAD")
  (phl:label 207.0 102.0 160.0 1.5 "库内主干道/消防通道（总宽不小于6m）")

  ;; D. road tanker loading zone
  (phl:rect 20.0 10.0 220.0 85.0 "ROAD")
  (phl:rect 26.0 16.0 214.0 79.0 "ROAD")
  (phl:rect 30.0 60.0 98.0 84.0 "BUILDING")
  (phl:label 64.0 72.0 62.0 1.8 "罐车等候缓冲区\P分车道排队/安全核验")
  (phl:rect 108.0 54.0 196.0 84.0 "BUILDING")
  (phl:label 152.0 81.0 84.0 1.5 "公路密闭底部装车棚（通过式，净空不小于5m）")
  (phl:building 113.0 60.0 128.0 76.0 "鹤位1\P92号")
  (phl:building 132.0 60.0 147.0 76.0 "鹤位2\P92号")
  (phl:building 151.0 60.0 166.0 76.0 "鹤位3\P95号")
  (phl:building 170.0 60.0 185.0 76.0 "鹤位4\P0号")
  (phl:building 108.0 26.0 138.0 44.0 "定量装车控制小屋")
  (phl:building 144.0 26.0 174.0 44.0 "装车泵房")
  (phl:label 63.0 42.0 62.0 1.5 "回车场（满足罐车回转）")
  (phl:line 40.0 0.0 40.0 10.0 "ROAD")
  (phl:mtext 43.0 5.0 45.0 1.5 "装车区独立出入口" "TEXT" 1)
  (phl:label 122.0 5.0 155.0 1.3 "4个鹤位为方案布置，最终数量由装车能力计算确定")

  ;; E. administration area
  (phl:building 244.0 55.0 304.0 86.0 "综合办公楼\P含中控控制室")
  (phl:building 311.0 55.0 351.0 86.0 "宿舍")
  (phl:building 358.0 55.0 394.0 86.0 "食堂")
  (phl:building 244.0 15.0 296.0 36.0 "行政车辆车库")
  (phl:building 365.0 11.0 387.0 28.0 "门卫")
  (phl:rect 311.0 17.0 349.0 38.0 "BUILDING")
  (phl:label 330.0 27.5 34.0 1.5 "人员集散/停车")
  (phl:line 300.0 8.0 355.0 8.0 "ROAD")
  (phl:line 355.0 0.0 355.0 8.0 "WALL")
  (phl:line 390.0 0.0 390.0 8.0 "WALL")
  (phl:label 372.5 5.0 30.0 1.8 "主大门")

  ;; F. municipal road, pipe corridors and fire-water ring
  (phl:rect 0.0 -14.0 420.0 -2.0 "ROAD")
  (phl:label 210.0 -8.0 260.0 1.8 "外部市政道路（具体道路名称及接驳点待选址测绘确认）")
  (phl:pline (list '(5.0 300.0) '(5.0 288.0) '(15.0 288.0) '(15.0 158.0) '(280.0 158.0) '(280.0 140.0)) "PIPE-IN" nil)
  (phl:mtext 18.0 286.0 65.0 1.5 "上游进库输油管道" "TEXT" 1)
  (phl:pline (list '(415.0 300.0) '(415.0 288.0) '(405.0 288.0) '(405.0 158.0) '(300.0 158.0)) "PIPE-OUT" nil)
  (phl:mtext 347.0 286.0 60.0 1.5 "管输出库主管" "TEXT" 1)
  (phl:pline (list '(16.0 162.0) '(404.0 162.0) '(404.0 106.0) '(280.0 106.0) '(280.0 94.0)) "FIRE-WATER" nil)
  (phl:mtext 20.0 160.0 95.0 1.4 "环状消防给水干管（示意）" "TEXT" 1)
  (phl:pline (list '(230.0 158.0) '(230.0 90.0) '(190.0 90.0) '(190.0 84.0)) "PIPE-IN" nil)
  (phl:mtext 233.0 128.0 45.0 1.4 "公路发油主管" "TEXT" 1)
  (phl:arrow 160.0 157.0 335.0 142.0 "DRAIN")
  (phl:label 250.0 151.0 150.0 1.3 "场地排水坡向事故应急池；坡度按竖向设计计算")

  ;; G. north arrow and wind information
  (phl:line 438.0 256.0 438.0 292.0 "WALL")
  (phl:line 438.0 292.0 433.0 282.0 "WALL")
  (phl:line 438.0 292.0 443.0 282.0 "WALL")
  (phl:label 438.0 297.0 14.0 3.0 "N")
  (phl:arrow 454.0 292.0 454.0 260.0 "DRAIN")
  (phl:mtext 458.0 276.0 34.0 1.5 "全年主导北风" "TEXT" 1)

  ;; H. right-side control notes, legend and title block
  (phl:rect 430.0 120.0 585.0 250.0 "WALL")
  (phl:label 507.5 244.0 145.0 2.5 "总图控制说明")
  (phl:mtext 435.0 235.0 145.0 1.55
    (strcat
      "1. 按GB 50074-2014划分四区。\P"
      "2. 0号柴油按丙A类固定顶罐绘制，不是丙B类。\P"
      "3. 10000m3储罐暂按D=30m、H=16.58m；同组罐壁净距12m（0.4D）。\P"
      "4. 防火堤至罐壁距离按不小于0.5H控制；有效容积另行核算。\P"
      "5. 行政区南置为方案位置。GB 50074第5.1.12条要求按全年最小频率风向下风侧校核，主导北风不能代替风玫瑰资料。\P"
      "6. H1-H4及场地最低标高须依据地形测量、设计洪潮水位和GB 50074第5.3.1条确定。")
    "TEXT" 1)

  (phl:rect 430.0 50.0 585.0 115.0 "WALL")
  (phl:label 507.5 110.0 145.0 2.5 "图例")
  (phl:line 438.0 101.0 458.0 101.0 "WALL") (phl:mtext 463.0 102.0 50.0 1.5 "实体围墙" "TEXT" 1)
  (phl:line 438.0 94.0 458.0 94.0 "ROAD") (phl:mtext 463.0 95.0 50.0 1.5 "道路/消防车道" "TEXT" 1)
  (phl:line 438.0 87.0 458.0 87.0 "DIKE") (phl:mtext 463.0 88.0 50.0 1.5 "防火堤/隔堤" "TEXT" 1)
  (phl:line 438.0 80.0 458.0 80.0 "PIPE-IN") (phl:mtext 463.0 81.0 50.0 1.5 "进库/公路发油管" "TEXT" 1)
  (phl:line 438.0 73.0 458.0 73.0 "PIPE-OUT") (phl:mtext 463.0 74.0 50.0 1.5 "管输出库主管" "TEXT" 1)
  (phl:line 438.0 66.0 458.0 66.0 "FIRE-WATER") (phl:mtext 463.0 67.0 50.0 1.5 "消防给水管网" "TEXT" 1)
  (phl:circle 448.0 58.0 4.0 "TANK") (phl:mtext 463.0 59.0 50.0 1.5 "立式储罐" "TEXT" 1)

  (phl:rect 430.0 -14.0 585.0 45.0 "WALL")
  (phl:line 430.0 25.0 585.0 25.0 "WALL")
  (phl:line 470.0 -14.0 470.0 45.0 "WALL")
  (phl:line 540.0 -14.0 540.0 25.0 "WALL")
  (phl:label 450.0 35.0 35.0 1.8 "项目名称")
  (phl:label 527.5 35.0 105.0 1.7 "广州黄埔穗东成品油库工艺设计")
  (phl:label 450.0 17.0 35.0 1.8 "图名")
  (phl:label 505.0 17.0 65.0 1.7 "总平面分区布置图")
  (phl:label 562.5 17.0 40.0 1.7 "图号 ZT-01")
  (phl:label 450.0 3.0 35.0 1.5 "毕业设计")
  (phl:label 505.0 3.0 65.0 1.5 "比例 1:1000")
  (phl:label 562.5 3.0 40.0 1.5 "2026-07")

  (phl:rect 0.0 -45.0 420.0 -18.0 "WALL")
  (phl:mtext 5.0 -21.0 410.0 1.45
    (strcat
      "设计依据：GB 50074-2014《石油库设计规范》；GB/T 50103-2010《总图制图标准》；SY/T 0003-2021《石油天然气工程制图规范》。\P"
      "建设地点：广州市黄埔区穗东街道附近。年均温22.6摄氏度，年降雨量2240mm，最大日降雨量346mm，主导风向偏北，年平均风速2.0m/s，最大风速32.8m/s。\P"
      "本图为毕业设计方案图。因缺少正式用地红线、1:500地形图、地勘、洪潮水位、全年风玫瑰图及市政接口资料，不得直接作为施工图或报批总图。")
    "TEXT" 1)

  ;; site dimensions and plot frame
  (phl:dim 0.0 306.0 420.0 306.0 210.0 312.0 "420m")
  (phl:dim -6.0 0.0 -6.0 300.0 -12.0 150.0 "300m")
  (phl:rect -18.0 -52.0 592.0 318.0 "WALL")

  (vla-EndUndoMark *phl-doc*)
  (setq savepath "D:\\毕业设计\\最终成品\\广州黄埔穗东油库总平面分区布置图-AutoCAD2012原生版.dwg")
  (vla-SaveAs *phl-doc* savepath)
  (vla-ZoomExtents acad)
  (princ "\nPHL oil-depot general layout completed and saved as native DWG.")
  (princ))

(princ "\nLoaded. Run command PHLZONING to draw the native oil-depot layout.")
(princ)
